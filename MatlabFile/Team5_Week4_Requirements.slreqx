# Team5_Week4_Requirements
[PI 제어기] 차간 거리 기반 모터 속도제어 시스템 개발

## Req_001: [기준 차량] 초기 Default 상태 (Functional)
기준 차량의 초기 Default 상태는 ACC ON 이어야 한다.

## Req_002: [전방 차량] 위치 값 (Functional)
전방 차량의 위치는 시나리오에 의해 0.01초 마다 주어진다.

## Req_003: [기준 차량] 위치 값 (Functional)
기준 차량의 초기 위치는 3이다.

## Req_004: [기준 차량] 초기 속도 값 (Functional)
초기 기준 차량 속도 값은 60으로 설정한다.

## Req_005: [기준 차량] 이벤트 트리거 발생 조건 (Functional)
전방 차와의 차간 거리가 20 이하로 진입할 경우 이벤트 트리거가 발생한다.

## Req_006: [기준 차량] 이벤트 트리거 발생 시 거리 기반 목표 속도 설정 (Functional)
이벤트 트리거 발생 시, 목표 거리 유지를 위해 PI 제어기로 기준 차량의 속도를 지정한다.

## Req_007: [기준 차량] 이벤트 트리거 발생 시 목표 속도 값 기반 현재 속도 제어 (Functional)
차량의 속도 출력값을 기반으로 목표 속도에 도달할 수 있도록 PI 제어기로 속도를 제어한다.

## Req_008: [PI 제어기] 계수 값 선정 (Functional)
각 PI제어기의 계수 값은 경험적으로 구한다.

## Req_009: [기능 검증] 시뮬레이션 (Functional)
본 시스템에 대한 기능 검증은 Matlab Simulink 기반 시뮬레이션으로 선행되어야 하며, 이후 실제 보드에 적용해야 한다.

## Req_010: [기타] 거리 측정 방법 (Functional)
차량 간 거리는 레이저 센서를 활용하여 측정한다.

## Req_011: [기능 검증] 테스트 시나리오 (Functional)
최소 3개이상의 전방 차량 위치 시나리오를 통해 기능을 검증해야 한다.
